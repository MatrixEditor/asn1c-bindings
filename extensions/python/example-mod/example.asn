ExampleModule DEFINITIONS AUTOMATIC TAGS  ::= BEGIN

-- basic types

Signed8 ::= INTEGER (-127..127)

NamedSigned8 ::= INTEGER {
    first(-1),
    second(0),
    third(1)
}

ExampleNamedBitString ::= BIT STRING {
    zero(0),
    one(1),
    two(2)
}

ExampleBoolean ::= BOOLEAN
ExampleBitString ::= BIT STRING
ExampleOctetString ::= OCTET STRING (SIZE(1..32))
ExampleNull ::= NULL
ExampleObjectIdentifier ::= OBJECT IDENTIFIER
ExampleRelativeOid ::= RELATIVE-OID
ExampleReal ::= REAL
ExampleUTF8String ::= UTF8String

ExampleChoice ::= CHOICE {
    foo         OCTET STRING,
    bar         INTEGER,
    baz         NamedSigned8,
    cReal       REAL,
    cBitString  BIT STRING,
    cBoolean    BOOLEAN,
    cNull       NULL,
    cOid        OBJECT IDENTIFIER,
    cRelOid     RELATIVE-OID,
    cEnum       ENUMERATED {
        ceA(1),
        ceB(2),
        ceC(3)
    },
    cNamedInt  INTEGER {
        cniA(1),
        cniB(2),
        cniC(3)
    },
    cNamedBitString  BIT STRING {
        cnbsA(1),
        cnbsB(2),
        cnbsC(3),
        cnbsOutOfBounds(1000)
    },
    cSeq        SEQUENCE {
        ciInt       INTEGER
    },
    cChoice     CHOICE {
        ciReal      REAL,
        ciBool      BOOLEAN,
        ciSeq       SEQUENCE {
            cis        INTEGER
        }
    }
}

ExampleOpenType ::= SEQUENCE {
        marker OBJECT IDENTIFIER,
        parameters ANY DEFINED BY marker OPTIONAL
}
ExampleExternal ::= EXTERNAL

ExampleSequence ::= SEQUENCE {
    sInt            INTEGER,
    sIntOpt         INTEGER OPTIONAL,
    sanInt          INTEGER {
        inamedA(1),
        inamedB(2),
        inamedC(3)
    },
    snInt           NamedSigned8,
    snIntOpt        NamedSigned8 OPTIONAL,
    sBoolOpt        BOOLEAN OPTIONAL,
    sBool           BOOLEAN,
    sBitStr         BIT STRING,
    snBitStr        BIT STRING {
        namedA(0),
        namedB(1),
        namedC(2)
    },
    sBitStrOpt      BIT STRING OPTIONAL,
    sOctetStr       ExampleOctetString,
    sOctetStrOpt    OCTET STRING OPTIONAL,
    sNull           NULL,
    sNullOpt        NULL OPTIONAL,
    sOid            OBJECT IDENTIFIER,
    sOidOpt         OBJECT IDENTIFIER OPTIONAL,
    sRelOid         RELATIVE-OID,
    sRelOidOpt      RELATIVE-OID OPTIONAL,
    sReal           REAL,
    sRealOpt        REAL OPTIONAL,
    sSeq            SEQUENCE {
        siInt           INTEGER,
        siSeq           SEQUENCE {
            siiInt          INTEGER
        }
    },
    sChoice         CHOICE {
        sicInt          INTEGER
    },
    sRefChoice  ExampleChoice,
    sSet ExampleSet
}

ExampleSet ::= SET {
    sInt        INTEGER,
    setSeq        SEQUENCE {
        siBool      BOOLEAN
    }
}

SeqOfRefType ::= SEQUENCE OF ExampleBoolean
SeqOfInt ::= SEQUENCE OF INTEGER
SeqOfReal ::= SEQUENCE OF REAL
SetOfNull ::= SET OF NULL
SeqOfOctetStr ::= SEQUENCE OF OCTET STRING
SeqOfOid ::= SEQUENCE OF OBJECT IDENTIFIER
SeqOfRelOid ::= SEQUENCE OF RELATIVE-OID
SeqOfBitStr ::= SEQUENCE OF BIT STRING
SeqOfStr ::= SEQUENCE OF UTF8String
SeqOfEnum ::= SEQUENCE OF ENUMERATED {
    seqOfEnumA(1),
    seqOfEnumB(2)
}

SeqOfSet ::= SEQUENCE OF SET {
    test    INTEGER
}

SeqOfNamedBitStr ::= SEQUENCE OF BIT STRING {
    test(1)
}

TestInnerSeqOfinSeq ::= SEQUENCE {
    test    INTEGER,
    inner   SEQUENCE OF INTEGER
}

TestInnerSeqOfSeqInSeq ::= SEQUENCE {
    -- inner anonymous sequence of anonymous sequences --
    test    INTEGER,
    inner   SEQUENCE OF SEQUENCE {
        innerTest    INTEGER
    }
}

Embedded-PDV ::= [UNIVERSAL 11] IMPLICIT SEQUENCE {
identification CHOICE {
  syntaxes SEQUENCE {
    abstract OBJECT IDENTIFIER,
	 transfer OBJECT IDENTIFIER }
	 -- Abstract and transfer syntax object identifiers --,
	 syntax OBJECT IDENTIFIER
	 -- A single object identifier for identification of the abstract
	 -- and transfer syntaxes --,
	 presentation-context-id INTEGER
	 -- (Applicable only to OSI environments)
	 -- The negotiated OSI presentation context identifies the
	 -- abstract and transfer syntaxes --,
	 context-negotiation SEQUENCE {
		presentation-context-id INTEGER,
		transfer-syntax OBJECT IDENTIFIER }
	 --(Applicable only to OSI environments)
	 -- Context-negotiation in progress, presentation-context-id
	 -- identifies only the abstract syntax
	 -- so the transfer syntax shall be specified --,
	 transfer-syntax OBJECT IDENTIFIER
	 -- The type of the value (for example, specification that it is
	 -- the value of an ASN.1 type)
	 -- is fixed by the application designer (and hence known to both
	 -- sender and receiver). This
	 -- case is provided primarily to support
	 -- selective-field-encryption (or other encoding
	 -- transformations) of an ASN.1	type --,
	 fixed NULL
	 -- The data value is the value of a fixed ASN.1 type (and hence
	 -- known to both sender
	 -- and receiver) --
  },
--   data-value-descriptor ObjectDescriptor OPTIONAL
  -- This provides human-readable identification of the class of the
  -- value --
  data-value OCTET STRING }

END
